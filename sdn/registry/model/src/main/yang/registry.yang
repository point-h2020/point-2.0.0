module registry {
    yang-version 1;
    namespace "urn:eu:point:registry";
    prefix registry;

	import opendaylight-inventory {prefix inv; revision-date 2013-08-19;}
    import yang-ext {prefix ext; revision-date "2013-07-09";}

    description "Registry configuration";

    revision "2015-07-22" {
        description "Initial version.";
    }


    container node-registry {
        list node-registry-entry {
            key "noneName";

            leaf noneName {
                type string;
            }
            leaf noneId {
                type string;
            }
        }
    }

    container link-registry {
        list link-registry-entry {
            key "linkName";

            leaf linkName {
                type string;
            }
            leaf linkId {
                type string;
            }
        }
    }

        container node-connector-registry {
            list node-connector-registry-entry {
                key "noneConnectorName";

                leaf noneConnectorName {
                    type string;
                }
                leaf srcNode {
                    type string;
                }
                leaf dstNode {
                    type string;
                }
            }
        }


}
